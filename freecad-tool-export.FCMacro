#
# This script will export the current FreeCad toolset into a Mach4 tooltable (at a hardcoded location, boo)
#

import sys
import json

if 'configparser' not in sys.modules:
	raise Exception("Please install the ConfigParser module with something like 'python -m pip install configparser' from your FreeCAD\bin directory")

# Load up the FreeCad tool library
toolLib_js = App.ParamGet("User parameter:BaseApp/Preferences/Mod/Path").GetString("ToolLibrary-Main")
toolLib = json.loads(toolLib_js)

# Create a new mach4 tooltable file. Configure it to contain tools for a mill with the properties we support.
mach4filename = "C:\\Mach4Hobby\\Profiles\\Sherline\\ToolTables\\tooltable.tls"
parser = configparser.ConfigParser()
parser.add_section("Properties")
parser.set("Properties", "Type", "Mill")
parser.set("Properties", "OptFields", "0")
fields = ((1, 'Length', 'Length', 'MTOOL_MILL_HEIGHT:Float(-1,4)'), 
			(3, 'Diameter', 'Dia', 'MTOOL_MILL_DIA:Float(-1,4)'), 
			(5, 'Desc', 'Description', 'MTOOL_MILL_DESC:String'),
			(2, 'LengthWear', 'Length Wear', 'MTOOL_MILL_HEIGHT_W:Float(-1,4)'),
			(4, 'DiameterWear', 'Diameter Wear', 'MTOOL_MILL_DIA_W:Float(-1,4)'))
parser.set("Properties", "Fields", str(len(fields)))
for fieldInfo in fields:
	parser.set("Properties", "Field%d" % fieldInfo[0], fieldInfo[1])
	parser.set("Properties", "FieldType%d" % fieldInfo[0], fieldInfo[3])
	parser.set("Properties", "FieldDesc%d" % fieldInfo[0], fieldInfo[2])

usrFields = ((1, 'Material', 'Material', 'String'), 
			(2, 'CuttingEdgeAngle', 'CuttingEdgeAngle', 'Float'))
parser.set("Properties", "UsrFields", str(len(usrFields)))
for fieldInfo in usrFields:
	parser.set("Properties", "UsrField%d" % fieldInfo[0], fieldInfo[1])
	parser.set("Properties", "UsrFieldType%d" % fieldInfo[0], fieldInfo[3])
	parser.set("Properties", "UsrFieldDesc%d" % fieldInfo[0], fieldInfo[2])

# Iterate over our FreeCad tools, generating and writing a corresponding Mach4 tool.
#for toolID in toolLib['Tools'].keys():
for toolID in range(1, 1000):
	toolSectionName = "Tool%s" % toolID
	if str(toolID) in toolLib['Tools'].keys():
		freeCadTool = toolLib['Tools'][str(toolID)]
		parser.add_section(toolSectionName)
		parser.set(toolSectionName, "Length" , str(freeCadTool['cuttingEdgeHeight']))
		parser.set(toolSectionName, "Diameter" , str(freeCadTool['diameter']))
		parser.set(toolSectionName, "Desc" , str(freeCadTool['name']))
		parser.set(toolSectionName, "LengthWear" , '0')
		parser.set(toolSectionName, "DiameterWear" , '0')
		parser.set(toolSectionName, "Material" , str(freeCadTool['material']))
		parser.set(toolSectionName, "CuttingEdgeAngle" , str(freeCadTool['cuttingEdgeAngle']))
	else:
		parser.add_section(toolSectionName)
		parser.set(toolSectionName, "Length" , '0')
		parser.set(toolSectionName, "Diameter" , '0')
		parser.set(toolSectionName, "Desc" , '')
		parser.set(toolSectionName, "LengthWear" , '0')
		parser.set(toolSectionName, "DiameterWear" , '0')
	#	parser.set(toolSectionName, "Material" , '')
	#	parser.set(toolSectionName, "CuttingEdgeAngle" , str(freeCadTool['cuttingEdgeAngle']))

parser.write(open(mach4filename, 'w'))
